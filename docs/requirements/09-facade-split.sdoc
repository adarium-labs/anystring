[DOCUMENT]
TITLE: String_Types Facade Split — Functional Requirements
REQ_PREFIX: FUNC-FACADE-

[GRAMMAR]
ELEMENTS:
- TAG: REQUIREMENT
  FIELDS:
  - TITLE: UID
    TYPE: String
    REQUIRED: True
  - TITLE: STATUS
    TYPE: String
    REQUIRED: False
  - TITLE: PRIORITY
    TYPE: String
    REQUIRED: False
  - TITLE: TITLE
    TYPE: String
    REQUIRED: False
  - TITLE: STATEMENT
    TYPE: String
    REQUIRED: False
  - TITLE: COMMENT
    TYPE: String
    REQUIRED: False
  - TITLE: RELATIONS
    TYPE: String
    REQUIRED: False

[SECTION]
TITLE: Context

[TEXT]
Feature: **FACADE-SPLIT** — Cleave OS-touching addons out of the
``String_Types`` facade into Ada child packages, so the strings layer
stays focused and SPARK-clean.

Today ``String_Types`` is a god-package: it re-exports the command-line
bridge (``Argument_Count``, ``Argument``, ``Set_Exit_Status``, …), the
environment-variable bridge, the ``Ada.Directories`` bridge and the
``Ada.Text_IO``-style bridge alongside the strings API. Consumers that
need only string operations are still forced to compile against
``Ada.Command_Line`` transitively, which (a) muddies the SPARK story —
``Anystrings`` is ``SPARK_Mode On`` but the addons are ``SPARK_Mode
Off`` — and (b) drags OS-coupling into every translation unit that says
``with String_Types;``.

This document covers **Layer 1** of a two-layer plan. Layer 1 splits the
*facade* — i.e. it moves the user-visible ``renames`` for the
command-line bridge out of ``String_Types`` and into the Ada child
package ``String_Types.Command_Line``. Layer 2 (out of scope here)
extracts the environment / directories / Text_IO bridges from the
``Anystrings`` generic formals into standalone per-backend packages,
so that a similar child-package split can be applied to them while
also satisfying the dependency-isolation invariant
(FUNC-FACADE-004).

The decision to keep environment / directories / Text_IO inside
``String_Types`` for Layer 1 is deliberate. Those three bridges are
declared as **generic formal parameters** of the ``Anystrings`` package
(``src/anystrings.ads``) and are instantiated via the per-backend
``<X>_String_Operations`` package, whose spec ``with``s
``Ada.Text_IO`` publicly. Moving only the *renames* into child
packages while leaving the generic structure unchanged would not
isolate the OS-unit dependency closure: every consumer of
``String_Types`` would still pull ``Ada.Text_IO``,
``Ada.Environment_Variables`` and ``Ada.Directories`` through the
``with String_Types -> with <X>_Strings -> with
<X>_String_Operations`` chain. Achieving true isolation for those
three requires restructuring the generic, which is Layer 2.

The command-line bridge, by contrast, is already a hand-rolled
per-backend package (``<X>_Command_Line``) that is **not** declared
as a formal of the ``Anystrings`` generic. Its facade can therefore
be split into a child package today with a clean dependency-isolation
guarantee.

All five bundled backends (``standard``, ``wide_string``,
``wide_wide_string``, ``uxstring``, ``vss``) MUST expose an identical
public surface for the new child package, mirroring the parity rule
already established for ``String_Types`` itself (FUNC-CMDLINE-009).

[/SECTION]

[SECTION]
TITLE: Facade Shape

[REQUIREMENT]
UID: FUNC-FACADE-001
STATUS: Approved
PRIORITY: Must
TITLE: String_Types is strings-only
STATEMENT: >>>
The package ``String_Types`` SHALL NOT re-export any subprogram, type,
constant, or subtype belonging to the command-line bridge feature
(FUNC-CMDLINE-001..009).

The strings-shaped surface — ``String_Type``, ``Character_Type``,
``Empty_String``, the comparison operators, conversion helpers
(``To_String_Type``, ``To_Latin_1``, ``To_UTF_8``, ``From_UTF_8`` and
their result types), the character-classification predicates, the
case-mapping subprograms, the substring-search and substitution
helpers, the prefix / suffix predicates, the Latin-1 lossy-detection
helpers, and the Hash function — SHALL remain accessible from
``String_Types`` directly.
<<<
COMMENT: >>>
This is the facade-cleanup invariant. After this change, a consumer
that needs only string operations writes ``with String_Types;`` and
inherits no command-line surface. The environment / directories /
Text_IO surfaces remain on ``String_Types`` for now (see Context for
why); they are scheduled for Layer 2.
<<<
RELATIONS: FUNC-CMDLINE-009

[REQUIREMENT]
UID: FUNC-FACADE-002
STATUS: Approved
PRIORITY: Must
TITLE: Command-line bridge exposed via String_Types.Command_Line child package
STATEMENT: >>>
The command-line bridge SHALL be exposed to user code as an Ada child
package of ``String_Types``, named ``String_Types.Command_Line``.

The child package SHALL re-export, by Ada ``renames`` or equivalent
mechanism, the entirety of the public surface introduced by
FUNC-CMDLINE-001..009:

- The argument-count function (FUNC-CMDLINE-001).
- The argument-access function (FUNC-CMDLINE-002, FUNC-CMDLINE-003).
- The command-name function (FUNC-CMDLINE-004).
- The exit-status subtype together with the ``Success`` and ``Failure``
  constants (FUNC-CMDLINE-005).
- Both ``Set_Exit_Status`` overloads (FUNC-CMDLINE-006, FUNC-CMDLINE-007).

The signatures of these declarations in ``String_Types.Command_Line``
SHALL be identical to those previously exposed by ``String_Types``;
only the package qualification at the call site changes.
<<<
COMMENT: >>>
"Identical signature" means same name, same parameter profile, same
return type, same enumeration-literal visibility. Existing call sites
that previously wrote ``Argument_Count`` (relying on ``use
String_Types;``) will now write ``Argument_Count`` (relying on ``use
String_Types.Command_Line;`` in addition).

The right-hand side of each ``renames`` differs per backend
(``Standard_Command_Line``, ``Wide_Command_Line``, …); this is the
existing per-backend package that already exists in
``src/strings/<dir>/<X>_command_line.ads/adb`` and is unchanged by
this feature.
<<<
RELATIONS: FUNC-CMDLINE-001, FUNC-CMDLINE-002, FUNC-CMDLINE-003, FUNC-CMDLINE-004, FUNC-CMDLINE-005, FUNC-CMDLINE-006, FUNC-CMDLINE-007

[REQUIREMENT]
UID: FUNC-FACADE-003
STATUS: Approved
PRIORITY: Must
TITLE: String_Types.Command_Line has identical surface across all five backends
STATEMENT: >>>
The package ``String_Types.Command_Line`` SHALL be present in every one
of the five bundled backend directories
(``src/strings/{standard,wide_string,wide_wide_string,uxstring,vss}/``)
and SHALL expose the same set of declarations with the same public
signatures across all five.

Only the right-hand side of each ``renames`` MAY differ between
backends (it MUST reference the local per-backend ``<X>_Command_Line``
implementation package).

User source code that ``with``s ``String_Types.Command_Line``,
optionally ``use``s it, and calls any of the declared subprograms
SHALL compile unchanged under any of the five backends.
<<<
COMMENT: >>>
This is the generalisation of FUNC-CMDLINE-009 to the new child
package. The parity rule is the same property that already governs
the rest of ``String_Types``: backend swap MUST be a build-time
source-directory substitution with zero consumer-side change.

Mechanically: the left-hand-side declarations of all five copies of
``string_types-command_line.ads`` MUST be byte-identical to each other
up to (a) the ``with`` clause and (b) the right-hand side of each
``renames``. No backend MAY add or remove a subprogram from the child
package.
<<<
RELATIONS: FUNC-FACADE-002, FUNC-CMDLINE-009

[/SECTION]

[SECTION]
TITLE: Dependency Isolation

[REQUIREMENT]
UID: FUNC-FACADE-004
STATUS: Approved
PRIORITY: Must
TITLE: Pure String_Types consumers do not pull Ada.Command_Line transitively
STATEMENT: >>>
A user compilation unit whose context clause is ``with String_Types;``
(without ``with String_Types.Command_Line;``) SHALL NOT have
``Ada.Command_Line`` in its semantic dependence closure.

Equivalently: the unit-list produced by ``gnatbind`` for a program
``with String_Types; procedure P is begin null; end P;`` SHALL NOT
contain a reference to ``Ada.Command_Line``.

This SHALL hold for all five bundled backends.
<<<
COMMENT: >>>
This is the dependency-isolation invariant — the core observable gain
of Layer 1. Before the split, the closure
``String_Types -> <X>_Command_Line -> Ada.Command_Line`` was forced
on every user. After the split, ``Ada.Command_Line`` enters the
closure only when the user explicitly opts in by saying
``with String_Types.Command_Line;``.

Verification is performed at the build-system level rather than at
runtime: a build-time check in
``examples/run_all_backends_demo.sh`` (or an equivalent script)
inspects the generated ``.ali`` file for the isolation-test program
and asserts the absence of ``Ada.Command_Line`` in the unit list.

Note that this requirement scopes only the command-line bridge.
The analogous guarantee for ``Ada.Environment_Variables``,
``Ada.Directories`` and ``Ada.Text_IO`` is NOT in scope for Layer 1
because their implementations are wired through ``Anystrings``
generic formals; achieving isolation for them requires the Layer 2
generic-restructure.
<<<
RELATIONS: FUNC-FACADE-001, FUNC-FACADE-002

[/SECTION]

[SECTION]
TITLE: Internal Layout

[REQUIREMENT]
UID: FUNC-FACADE-005
STATUS: Approved
PRIORITY: Should
TITLE: Per-backend implementation packages keep their existing flat names
STATEMENT: >>>
The existing per-backend implementation packages
``Standard_Command_Line``, ``Wide_Command_Line``,
``Wide_Wide_Command_Line``, ``UXString_Command_Line`` and
``VSS_Command_Line`` (one per backend, located at
``src/strings/<dir>/<prefix>_command_line.{ads,adb}``) SHALL retain
their current names and file paths.

These packages SHALL NOT be made Ada child packages of either
``Anystrings`` or ``String_Types``; they remain top-level
implementation units.
<<<
COMMENT: >>>
The implementation packages are not user-visible — consumers go
through ``String_Types.Command_Line``. Renaming them to mirror the
new facade hierarchy (e.g. ``Anystrings.Command_Line.Standard``)
would churn the directory-swap mechanism, which relies on per-backend
flat source directories under ``src/strings/<dir>/``. The cost is
high and the benefit is internal-only.

The implementation packages MAY be relocated or restructured in a
future refactor (Layer 2 or later); this requirement only mandates
the *Layer 1* status quo.
<<<
RELATIONS: FUNC-FACADE-002

[/SECTION]

[SECTION]
TITLE: Future Work (Layer 2)

[REQUIREMENT]
UID: FUNC-FACADE-006
STATUS: Approved
PRIORITY: Must
TITLE: Layer 2 umbrella — Environment / Directories / Text_IO bridges leave the Anystrings generic
STATEMENT: >>>
The environment, filesystem (``Ada.Directories``) and Text_IO bridges
SHALL be extracted out of the ``Anystrings`` generic formals into
standalone per-backend implementation packages following the existing
``<X>_Command_Line`` pattern. The corresponding generic formal
subprograms SHALL be removed from ``src/anystrings.ads`` and the
matching ``with function ... =>`` actuals SHALL be removed from
every backend's ``<X>_strings.ads`` instantiation.

The detailed per-addon requirements are FUNC-FACADE-007 (Environment),
FUNC-FACADE-008 (Directories) and FUNC-FACADE-009 (Text_IO); the
extended dependency-isolation invariant is NFR-FACADE-002.
<<<
COMMENT: >>>
This is the umbrella requirement under which Layer 2 is delivered.
Promoted from ``Draft / Could`` (Layer 1 placeholder) to
``Approved / Must`` because Layer 2 is now in flight. The three
per-addon FUNC requirements decompose the work, while NFR-FACADE-002
extends the dependency-isolation guarantee originally introduced by
FUNC-FACADE-004 (cmdline) to cover the three additional OS units.
<<<
RELATIONS: FUNC-FACADE-001, FUNC-FACADE-004

[/SECTION]

[SECTION]
TITLE: Layer 2 — Per-addon Facade Splits

[REQUIREMENT]
UID: FUNC-FACADE-007
STATUS: Approved
PRIORITY: Must
TITLE: Environment bridge exposed via String_Types.Environment child package
STATEMENT: >>>
The environment-variable bridge SHALL be exposed to user code as an
Ada child package of ``String_Types``, named
``String_Types.Environment``.

The five generic formal subprograms wiring the environment bridge
through ``Anystrings`` (``Environment_Value``, ``Environment_Exists``,
``Environment_Set``, ``Environment_Clear``, ``Environment_Clear_All``,
``Environment_Iterate``) and the corresponding ``with function`` /
``with procedure`` actuals in every ``<X>_strings.ads`` SHALL be
removed.

For each backend ``<X>`` in {``standard``, ``wide_string``,
``wide_wide_string``, ``uxstring``, ``vss``} a standalone
per-backend implementation package ``<X>_Environment`` SHALL exist
at ``src/strings/<X>/<prefix>_environment.{ads,adb}`` exporting the
full environment surface as concrete subprograms operating on
``String_Type`` (with the per-backend ``String_Type`` of that
backend).

The Ada child package ``String_Types.Environment`` SHALL be present
in every backend directory and SHALL re-export, by Ada ``renames``
(or equivalent), the entirety of the environment public surface:

- ``Env_Processor`` access-to-procedure type.
- ``Env_Filter`` access-to-function type.
- ``Get_Env`` (single-argument: returns empty on absence).
- ``Get_Env`` (two-argument: explicit default).
- ``Env_Exists``.
- ``Set_Env``.
- ``Clear_Env`` (per-variable).
- ``Clear_Env`` (no-argument: clears all).
- ``Iterate_Env`` (with ``Process`` only).
- ``Iterate_Env`` (with ``Include`` filter and ``Process``).

The left-hand-side declarations across the five copies of
``string_types-environment.ads`` SHALL be byte-identical up to the
``with`` clauses and the right-hand-side rename targets.

The build-time switch ``ANYSTRING_WIDE_ENV_ENCODING`` (with values
``utf_8`` default and ``latin_1``) SHALL be preserved. The two
selector source directories ``src/strings/wide_env_encoding/utf_8``
and ``src/strings/wide_env_encoding/latin_1`` SHALL continue to
work unchanged; the ``wide_string`` and ``wide_wide_string``
backends' new ``<X>_Environment`` packages SHALL consume the
selected ``anystrings_internal_wide_environment_encoding`` package
the same way the prior ``<X>_String_Operations`` implementations
did.
<<<
COMMENT: >>>
The right-hand side of each ``renames`` resolves per backend:
``Standard_Environment``, ``Wide_Environment``,
``Wide_Wide_Environment``, ``UXString_Environment``,
``VSS_Environment``.

This requirement does NOT cover dependency isolation — that is
NFR-FACADE-002. It only mandates the surface placement and parity.
<<<
RELATIONS: FUNC-FACADE-001, FUNC-FACADE-006, NFR-FACADE-002

[REQUIREMENT]
UID: FUNC-FACADE-008
STATUS: Approved
PRIORITY: Must
TITLE: Directories bridge exposed via String_Types.Directories child package
STATEMENT: >>>
The filesystem (``Ada.Directories``) bridge SHALL be exposed to user
code as an Ada child package of ``String_Types``, named
``String_Types.Directories``.

The generic formal type ``File_Kind`` and the five generic formal
subprograms wiring the filesystem bridge through ``Anystrings``
(``Path_Exists``, ``Path_Kind``, ``Create_Directory_Path``,
``Delete_File_Path``, ``Rename_Path``) and their actuals in every
``<X>_strings.ads`` SHALL be removed.

For each backend ``<X>`` a standalone per-backend implementation
package ``<X>_Directories`` SHALL exist at
``src/strings/<X>/<prefix>_directories.{ads,adb}`` exporting:

- The ``File_Kind`` enumeration type (with literals ``Directory``,
  ``Ordinary_File``, ``Special_File`` in that order — matching
  ``Ada.Directories.File_Kind``).
- ``Exists`` / ``Kind`` / ``Create_Directory`` / ``Delete_File`` /
  ``Rename`` operating on the per-backend ``String_Type``.

The Ada child package ``String_Types.Directories`` SHALL be present
in every backend directory and SHALL re-export the
following public surface:

- ``File_Kind`` subtype, plus the three named constants
  ``Directory``, ``Ordinary_File``, ``Special_File`` as constants of
  type ``File_Kind`` (so they are visible via ``use``).
- ``"="`` on ``File_Kind``.
- ``Exists``, ``Kind``, ``Create_Directory``, ``Delete_File``,
  ``Rename``.

The five filesystem operations SHALL remain TOTAL by contract:
any runtime error from ``Ada.Directories`` SHALL be absorbed and
translated into ``False`` / ``Special_File`` returns (no exception
SHALL propagate across the ``String_Types.Directories`` boundary).
This preserves the FUNC-DIR-001..008 / NFR-DIR-001..005 contract
inherited from the current implementation.

The left-hand-side declarations across the five copies of
``string_types-directories.ads`` SHALL be byte-identical up to the
``with`` clauses and the right-hand-side rename targets.
<<<
COMMENT: >>>
Right-hand-side targets per backend: ``Standard_Directories``,
``Wide_Directories``, ``Wide_Wide_Directories``,
``UXString_Directories``, ``VSS_Directories``.

The path-encoding helper used by each backend's ``Path_*`` /
``*_Path`` implementations is unchanged (see ``src/strings/AGENTS.md``
"Filesystem boundary path encoding" table). The refactor is purely
structural.
<<<
RELATIONS: FUNC-FACADE-001, FUNC-FACADE-006, NFR-FACADE-002

[REQUIREMENT]
UID: FUNC-FACADE-009
STATUS: Approved
PRIORITY: Must
TITLE: Text_IO bridge exposed via String_Types.Text_IO child package
STATEMENT: >>>
The Text_IO bridge SHALL be exposed to user code as an Ada child
package of ``String_Types``, named ``String_Types.Text_IO``.

The two generic formal types ``File_Type`` (limited private) and
``File_Mode`` (private), the three formal ``File_Mode`` constants
(``In_File_Mode``, ``Out_File_Mode``, ``Append_File_Mode``) and the
fourteen generic formal subprograms wiring the Text_IO bridge through
``Anystrings`` (``Create_File``, ``Open_File``, ``Close_File``,
``Is_Open_File``, ``Current_Input_File``, ``Current_Output_File``,
``Set_Input_File``, ``Set_Output_File``, ``Put_File``,
``Get_Line_File``, ``New_Line_File``, ``End_Of_File_File``) and their
actuals in every ``<X>_strings.ads`` SHALL be removed.

For each backend ``<X>`` a standalone per-backend implementation
package ``<X>_Text_IO`` SHALL exist at
``src/strings/<X>/<prefix>_text_io.{ads,adb}`` exporting:

- The ``File_Type`` (limited private) and ``File_Mode`` types.
- The three ``File_Mode`` constants ``In_File``, ``Out_File``,
  ``Append_File``.
- ``Create``, ``Open``, ``Close``, ``Is_Open``, ``Current_Input``,
  ``Current_Output``, ``Set_Input``, ``Set_Output``, ``Put`` (two
  overloads: standard-out and file-targeted), ``Put_Line`` (two
  overloads), ``Get_Line`` (four overloads), ``New_Line`` (two
  overloads), ``End_Of_File`` (two overloads).

The Ada child package ``String_Types.Text_IO`` SHALL be present in
every backend directory and SHALL re-export the same public surface.

The left-hand-side declarations across the five copies of
``string_types-text_io.ads`` SHALL be byte-identical up to the
``with`` clauses and the right-hand-side rename targets.

Text_IO semantics continue to follow the selected backend's native
Ada I/O family (``Ada.Text_IO`` for standard / uxstring,
``Ada.Wide_Text_IO`` for wide_string, ``Ada.Wide_Wide_Text_IO`` for
wide_wide_string; VSS continues to delegate to ``Ada.Text_IO`` via
the VSS conversion path). External-encoding and newline behaviour
are backend-specific at this boundary — unchanged from Layer 1.
<<<
COMMENT: >>>
Right-hand-side targets per backend: ``Standard_Text_IO``,
``Wide_Text_IO``, ``Wide_Wide_Text_IO``, ``UXString_Text_IO``,
``VSS_Text_IO``.

This is the largest of the three Layer 2 surface moves; the
sub-iteration order in the Layer 2 work plan (Env → Dirs → Text_IO)
puts it last so the migration patterns are well rehearsed by the
time Text_IO's broader consumer footprint is touched.
<<<
RELATIONS: FUNC-FACADE-001, FUNC-FACADE-006, NFR-FACADE-002

[/SECTION]

[SECTION]
TITLE: Layer 2 — Dependency Isolation (NFR)

[REQUIREMENT]
UID: NFR-FACADE-002
STATUS: Approved
PRIORITY: Must
TITLE: Pure String_Types consumers do not pull Ada.Environment_Variables / Ada.Directories / Ada.Text_IO transitively
STATEMENT: >>>
A user compilation unit whose context clause is ``with String_Types;``
(without any of ``with String_Types.Command_Line;``,
``with String_Types.Environment;``, ``with String_Types.Directories;``
or ``with String_Types.Text_IO;``) SHALL NOT have any of the
following Ada library units in its semantic dependence closure:

- ``Ada.Command_Line`` (already required by FUNC-FACADE-004).
- ``Ada.Environment_Variables``.
- ``Ada.Directories``.
- ``Ada.Text_IO``, ``Ada.Wide_Text_IO``, ``Ada.Wide_Wide_Text_IO``.

Equivalently: the binder-listing (or the ``.ali`` unit list) for a
program

    with String_Types; procedure P is begin null; end P;

SHALL NOT contain any of ``ada.command_line``, ``a-comlin``,
``ada.environment_variables``, ``a-envvar``, ``ada.directories``,
``a-direct``, ``ada.text_io``, ``a-textio``,
``ada.wide_text_io``, ``a-witeio``, ``ada.wide_wide_text_io``,
``a-ztexio``.

This SHALL hold for all five bundled backends.
<<<
COMMENT: >>>
This is the extended facade-isolation invariant — the core observable
gain of Layer 2. It supersedes FUNC-FACADE-004 by widening the
forbidden-OS-unit set from a single unit (``Ada.Command_Line``) to
four families.

Verification is performed at the build-system level: the runner
``examples/run_all_backends_demo.sh`` greps the ``.ali`` file of the
``Anystrings_Facade_Isolation`` test program for any of the listed
substrings and fails the script if any is present. The check runs
once per backend.

The Wide_Text_IO and Wide_Wide_Text_IO names are included because
the ``wide_string`` and ``wide_wide_string`` backends previously
pulled those units (not ``Ada.Text_IO``); after Layer 2 they must
not appear in the ``String_Types``-only closure either.
<<<
RELATIONS: FUNC-FACADE-001, FUNC-FACADE-004, FUNC-FACADE-006, FUNC-FACADE-007, FUNC-FACADE-008, FUNC-FACADE-009

[/SECTION]
