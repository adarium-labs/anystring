[DOCUMENT]
TITLE: Anystrings Requirements Index
REQ_PREFIX: VIS-

[GRAMMAR]
ELEMENTS:
- TAG: REQUIREMENT
  FIELDS:
  - TITLE: UID
    TYPE: String
    REQUIRED: True
  - TITLE: STATUS
    TYPE: String
    REQUIRED: False
  - TITLE: PRIORITY
    TYPE: String
    REQUIRED: False
  - TITLE: TITLE
    TYPE: String
    REQUIRED: False
  - TITLE: STATEMENT
    TYPE: String
    REQUIRED: False
  - TITLE: COMMENT
    TYPE: String
    REQUIRED: False
  - TITLE: RELATIONS
    TYPE: String
    REQUIRED: False

[SECTION]
TITLE: About this document

[TEXT]
This document is the root of the anystrings requirements tree.  It
provides the UID naming conventions and serves as the entry point for
all requirement files in this directory.

[TEXT]
UID scheme:

- **VIS-NNN**           — Vision / scope requirements
- **FUNC-UTF8-NNN**     — UTF-8 generic-API functional requirements
- **NFR-UTF8-NNN**      — UTF-8 non-functional requirements
- **FUNC-CMDLINE-NNN**  — Command-line access functional requirements
- **FUNC-CONV-NNN**     — Library-wide conversion semantics functional requirements
- **NFR-CONV-NNN**      — Library-wide conversion semantics non-functional requirements
- **FUNC-DIR-NNN**     — Filesystem boundary (Ada.Directories) functional requirements
- **NFR-DIR-NNN**      — Filesystem boundary (Ada.Directories) non-functional requirements
- **FUNC-FACADE-NNN**  — String_Types facade-split (Layer 1) functional requirements
- **NFR-FACADE-NNN**   — String_Types facade-split (Layer 2) non-functional requirements
- **FUNC-WIDTH-NNN**   — Display-width / grapheme-cluster boundary functional requirements
- **NFR-WIDTH-NNN**    — Display-width / grapheme-cluster boundary non-functional requirements

All UIDs use zero-padded three-digit ordinals (001, 002, …).  New UID
prefixes are added here as new feature areas are specified.

[/SECTION]

[SECTION]
TITLE: Documents

[TEXT]
- docs/requirements/02-utf8-boundary-api.sdoc — UTF-8 generic API functional requirements
- docs/requirements/03-utf8-boundary-api-nfr.sdoc — UTF-8 generic API non-functional requirements
- docs/requirements/04-cmdline.sdoc — Command-line access functional requirements
- docs/requirements/05-conversion-semantics.sdoc — Library-wide UTF-8 / Latin-1 conversion semantics functional requirements
- docs/requirements/06-conversion-semantics-nfr.sdoc — Library-wide UTF-8 / Latin-1 conversion semantics non-functional requirements
- docs/requirements/07-filesystem-boundary.sdoc — Filesystem boundary (Ada.Directories) functional requirements
- docs/requirements/08-filesystem-boundary-nfr.sdoc — Filesystem boundary (Ada.Directories) non-functional requirements
- docs/requirements/09-facade-split.sdoc — String_Types facade-split (Layer 1 + Layer 2) functional and non-functional requirements
- docs/requirements/10-width-boundary.sdoc — Display-width / grapheme-cluster boundary functional and non-functional requirements (UMWI-backed, opt-in)

[/SECTION]
